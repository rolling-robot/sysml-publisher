package Other {
    part def md {
        rep language "markdown"
            /* *not* asciidoc */
    }
    part def up {
        rep language "AsciiDoc"
            /* upper-case language name */
    }
}
